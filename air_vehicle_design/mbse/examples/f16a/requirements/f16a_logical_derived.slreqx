# f16a_logical_derived
Design-decision requirements for the three F-16A logical roles whose realization is not decided. A role with more than one credible realization is an open question, not a settled part (D-002). The question is recorded at L. The decision is made at P, where the candidates carry numbers (D-001). Three Physical-layer trade studies (physical/F16AEngineTradeStudy.m, F16AFlightControlsTradeStudy.m and F16AAirframeTradeStudy.m) score the concrete, parameterized candidates. Each trade study answers one question.

## REQ_F16A_LOGICAL: F-16A logical design decisions (Container)
Root container for the design decisions about the Logical-layer roles. Each requirement names three things: a role with more than one credible solution option, the kinds given for that role, and the Physical-layer trade study that selects one of them. You can read the answer in two places. The first is the Implement link that the trade study creates from the winning kind in logical/F16A_Logical.slx to the requirement. The second is the Rationale.Justification of that winner in physical/F16A_Physical.slx. By design, no requirement in this set contains a weight, a score or a winner. The weights are in each trade script. The requirement states the question before a trade study answers it. Thus an outcome stated here would be a claim, not a record (D-037, D-040).
- Keywords: draft, derived, logical, decision

### REQ_F16A_L01: Propulsion: single-engine or twin-engine installation? (Functional)
Exactly one kind shall realize the PropulsionSystem role: SingleEngine or TwinEngine. The Logical layer gives these two kinds. The Physical-layer trade study physical/F16AEngineTradeStudy.m makes the choice. It scores the concrete, parameterized engine candidates that realize each kind. This requirement states the decision to make. It does not contain the answer (D-040).
- Rationale: This decision is worth stating, not assuming, for these reasons. A twin installation gives engine-out survivability. A single installation avoids the installed mass and the complexity of a duplicated engine and accessory group.
- Keywords: draft, derived, logical, decision

### REQ_F16A_L02: Flight control: fly-by-wire or hydro-mechanical? (Functional)
Exactly one kind shall realize the FlightControlSystem role: FlyByWire or HydroMechanical. The Logical layer gives these two kinds. The Physical-layer trade study physical/F16AFlightControlsTradeStudy.m makes the choice. It scores the concrete, parameterized flight-control candidates that realize each kind. This requirement states the decision to make. It does not contain the answer (D-040).
- Rationale: This decision is worth stating, not assuming. REQ_F16A_025 requires a negative static margin, and only a control system that can supply artificial stability makes that margin flyable.
- Keywords: draft, derived, logical, decision

### REQ_F16A_L03: Airframe: blended cranked-delta or conventional trapezoidal wing? (Functional)
Exactly one kind shall realize the Airframe role: BlendedCrankedDelta or ConventionalTrapWing. The Logical layer gives these two kinds. The Physical-layer trade study physical/F16AAirframeTradeStudy.m makes the choice. It scores the concrete, parameterized airframe candidates that realize each kind. This requirement states the decision to make. It does not contain the answer (D-040).
- Rationale: This decision is worth stating, not assuming, for these reasons. A blended cranked-delta planform gives high-alpha and sustained-turn performance. A conventional trapezoidal wing is a better-understood shape with less aerodynamic development risk.
- Keywords: draft, derived, logical, decision
