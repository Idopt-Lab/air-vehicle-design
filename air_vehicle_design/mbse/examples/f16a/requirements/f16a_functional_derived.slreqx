# f16a_functional_derived
Derived functional and capability requirements for the F-16A. They were identified during the Functional-layer (RFLP F) analysis. The values are PLACEHOLDERS: the quantitative acceptance criteria are not yet defined. This set is kept separate from the sizing-derived set (f16a.slreqx) to keep the original provenance.

## REQ_F16A_DERIVED: F-16A derived functional requirements (placeholders) (Container)
Root container for the functional requirements derived during the RFLP Functional-layer analysis. Each requirement captures an aircraft function that is necessary to complete the mission and that the sizing-derived requirement set does not cover. The values are PLACEHOLDERS (TBD).
- Keywords: draft, derived, placeholder

### REQ_F16A_D01: Maneuvering capability (Functional)
The aircraft shall provide sufficient maneuvering capability (attitude and flight-path control) to fly the mission profile and the combat maneuvers. PLACEHOLDER: the quantitative criteria are TBD (for example, roll rate, sustained and instantaneous turn rate, and control authority across the flight envelope).
- Rationale: Derived from the functional analysis. The Maneuver function is necessary to fly the mission profile and the F2T2EA engagement. The sizing-derived requirement set does not cover this function.
- Keywords: draft, derived, placeholder, todo

### REQ_F16A_D02: Fuel management (Functional)
The aircraft shall manage the onboard fuel (storage, sequencing, feed and transfer) to complete the mission profile with the required reserves. PLACEHOLDER: the quantitative criteria are TBD (usable fuel, feed sequencing, CG-neutral transfer).
- Rationale: Derived from the functional analysis. The ManageFuel function is necessary to complete the mission profile. The sizing-derived requirement set does not cover this function.
- Keywords: draft, derived, placeholder, todo

### REQ_F16A_D03: Navigation (Functional)
The aircraft shall determine its position and follow the planned mission route. PLACEHOLDER: the quantitative criteria are TBD (position accuracy, waypoint tracking, route-following tolerance).
- Rationale: Derived from the functional analysis. The Navigate function is necessary to fly the mission route. The sizing-derived requirement set does not cover this function.
- Keywords: draft, derived, placeholder, todo

### REQ_F16A_D04: Communication and identification (Functional)
The aircraft shall exchange voice and data communications. It shall identify friend or foe (IFF). PLACEHOLDER: the quantitative criteria are TBD (datalink availability, communication range, IFF interrogation and response).
- Rationale: Derived from the functional analysis. The Communicate function is necessary to operate in a networked battlespace. The sizing-derived requirement set does not cover this function.
- Keywords: draft, derived, placeholder, todo

### REQ_F16A_D05: Find targets (Functional)
The aircraft shall detect potential targets in the combat area. PLACEHOLDER: the quantitative criteria are TBD (detection range, sensor field of regard).
- Rationale: Derived from the functional analysis. The Find step of the F2T2EA kill chain is necessary for combat. The sizing-derived requirement set does not cover this step.
- Keywords: draft, derived, placeholder, todo

### REQ_F16A_D06: Fix targets (Functional)
The aircraft shall determine the location and the identity of detected targets to a fix. PLACEHOLDER: the quantitative criteria are TBD (geolocation accuracy, identification confidence).
- Rationale: Derived from the functional analysis. The Fix step of the F2T2EA kill chain is necessary for combat. The sizing-derived requirement set does not cover this step.
- Keywords: draft, derived, placeholder, todo

### REQ_F16A_D07: Track targets (Functional)
The aircraft shall maintain track on the targets that it fixed. PLACEHOLDER: the quantitative criteria are TBD (number of simultaneous tracks, track continuity).
- Rationale: Derived from the functional analysis. The Track step of the F2T2EA kill chain is necessary for combat. The sizing-derived requirement set does not cover this step.
- Keywords: draft, derived, placeholder, todo

### REQ_F16A_D08: Target and assign weapons (Functional)
The aircraft shall prioritize and designate targets. It shall assign weapons. PLACEHOLDER: the quantitative criteria are TBD (targeting timeline, weapon-target pairing).
- Rationale: Derived from the functional analysis. The Target step of the F2T2EA kill chain is necessary for combat. The sizing-derived requirement set does not cover this step.
- Keywords: draft, derived, placeholder, todo

### REQ_F16A_D09: Assess engagement (Functional)
The aircraft shall assess engagement results (battle damage assessment). PLACEHOLDER: the quantitative criteria are TBD (BDA reporting, re-attack decision support).
- Rationale: Derived from the functional analysis. The Assess step of the F2T2EA kill chain is necessary for combat. The sizing-derived requirement set does not cover this step.
- Keywords: draft, derived, placeholder, todo
