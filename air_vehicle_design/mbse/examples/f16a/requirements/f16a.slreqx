# f16a
Top-level aircraft requirements for the F-16A. They come from the Brandt F-16A reference sizing model (sizing/VnV/BrandtF16A) and are cross-referenced against the Main tab of Brandt-F16-A.xls. Only Excel input cells become requirement values. There is one documented exception: REQ_F16A_025. Its -6 %MAC static-margin floor is design intent, not a workbook cell, and it is an Estimate (D-030). Its upper bound is now a strict SM < 0, which is a definition, not a figure. DRAFT, for review in the RFLP Requirements phase.

## REQ_F16A_000: F-16A top-level aircraft requirements (Container)
Root container for the top-level requirements. These requirements come from the Brandt F-16A sizing analysis (VnV/BrandtF16A) and the Main tab of Brandt-F16-A.xls.
- Keywords: draft

### REQ_F16A_MISSION: Mission profile requirements (Container)
- Keywords: draft

#### REQ_F16A_001: Takeoff condition (Functional)
When the aircraft executes the Takeoff segment, it shall operate at sea level (Altitude = 0 ft, Main!K33, input) with 100% afterburner (Main!K36, input). End Mach (0.282, Main!K35) is a computed liftoff speed (=Miss!B5). It is not a given input.
- Rationale: Sets the ground-roll flight condition that is used to size takeoff thrust and field length.
- Keywords: draft

#### REQ_F16A_002: Acceleration condition (Functional)
While in the Accel segment, the aircraft shall accelerate at an altitude of 10,000 ft (Main!L33, input) to an end Mach number of 0.87 (Main!L35, input). It shall use dry power, 0% afterburner (Main!L36, input). All three values are direct Excel inputs, not formulas.
- Rationale: Defines the dry-power acceleration leg from the takeoff climb-out to the design cruise Mach.
- Keywords: draft

#### REQ_F16A_003: Climb condition (Functional)
While in the Climb segment, the aircraft shall climb to an altitude of 40,000 ft (Main!M33, input) with dry power, 0% afterburner (Main!M36, input). End Mach (0.87, Main!M35) comes from the Accel segment through a formula (=L35). It is not an independent input.
- Rationale: Sets the target cruise altitude for all later cruise, dash, combat and egress legs.
- Keywords: draft

#### REQ_F16A_004: Outbound cruise condition (Functional)
While in the Cruise segment, the aircraft shall cruise with dry power, 0% afterburner (Main!N36, input). Altitude (40,000 ft) and Mach (0.87) come from the Climb and Accel segments through formulas (=M33, =M35). They are not independent inputs in this segment.
- Rationale: Specifies dry-power cruise to the combat area.
- Keywords: draft

#### REQ_F16A_005: Dash condition (Functional)
While in the Dash segment, the aircraft shall use 50% afterburner (Main!P36, input) to fly a distance of 50 nm (Main!P38, input). Altitude and Mach come from the Cruise segment through formulas.
- Rationale: Defines the distance and the power setting of the ingress dash leg, which uses partial afterburner.
- Keywords: draft

#### REQ_F16A_006: Combat condition (Functional)
When the aircraft enters the Combat segment, it shall operate at an altitude of 25,000 ft (Main!R33, input) for 2 min (Main!R39, input). During this time, it shall release its expendable payload (Miss!I10, 4400 lb). A formula sets %AB (Main!R36 = P36 = 50%) to the afterburner setting of the Dash segment. It is not an independent input in this segment.
- Rationale: Sets the duration of combat persistence, the combat altitude and the store-release event.
- Keywords: draft

#### REQ_F16A_007: Egress condition (Functional)
While in the Egress segment, the aircraft shall use dry power, 0% afterburner (Main!S36, input), to fly a distance of 50 nm (Main!S38, input) at an altitude of 40,000 ft (Main!S33, input).
- Rationale: Defines the dry-power return leg from the combat area.
- Keywords: draft

#### REQ_F16A_008: Return cruise condition (Functional)
While in the Cruise2 segment (the second cruise leg, toward base), the aircraft shall cruise with dry power, 0% afterburner (Main!V36, input). Altitude and Mach come from earlier segments through formulas. They are not independent inputs in this segment. The distance for this leg (Main!V38) is a closure value that Excel computes to balance the overall mission distance budget. It is not a directly given input.
- Rationale: Specifies dry-power cruise on the return leg. Unlike Dash and Egress, the range of this leg is a computed closure value, not a design input.
- Keywords: draft

#### REQ_F16A_009: Loiter condition (Functional)
While in the Loiter segment, the aircraft shall loiter at an altitude of 10,000 ft (Main!W33, input) and Mach 0.30 (Main!W35, input). It shall loiter for 20 min (Main!W39, input) with 0% afterburner (Main!W36, input).
- Rationale: Provides the reserve for holding or approach delay before landing.
- Keywords: draft

#### REQ_F16A_010: Landing condition (Functional)
While in the Landing segment, the aircraft shall land at sea level (Altitude = 0 ft, Main!X33, input). The landing ground-roll distance (Main!X36 = 2884.95 ft) is a value that Excel computes (=Miss!O6). It is not a given input. Instead, the Point Performance container gives the available landing field length as a design input (S_land = 4000 ft).
- Rationale: Sets the sea-level landing condition. The actual ground-roll performance is verified against the landing field-length requirement.
- Keywords: draft

### REQ_F16A_PERF: Point performance requirements (Container)
- Keywords: draft

#### REQ_F16A_011: Max-Mach point performance (Functional)
The aircraft shall be capable of sustained level flight (Ps = 0, Main!X3, input) at Mach 1.6 (Main!U3, input). This applies at these conditions: weight fraction W/W_TO = 0.8997 (Main!S3, computed elsewhere from fuel-state cells), altitude 36,000 ft (Main!T3, input), load factor n = 1 (Main!V3, input) and 100% afterburner (Main!W3, input).
- Rationale: Defines the top-speed design point on the T/W-vs-W/S constraint diagram (Consts row 23).
- Keywords: draft

#### REQ_F16A_012: Cruise point performance (Functional)
The aircraft shall be capable of sustained level flight (Ps = 0, Main!X4, input) at Mach 0.87 (Main!U4, input). This applies at these conditions: weight fraction W/W_TO = 0.8997 (Main!S4), altitude 36,000 ft (Main!T4, input), load factor n = 1 (Main!V4, input) and 0% afterburner (Main!W4, input).
- Rationale: Defines the dry-power cruise design point on the constraint diagram (Consts row 24).
- Keywords: draft

#### REQ_F16A_013: Max-altitude point performance (Functional)
The aircraft shall be capable of sustained level flight (Ps = 0, Main!X5, input) at an altitude of 50,000 ft (Main!T5, input) and Mach 0.87 (Main!U5, input). This applies at these conditions: weight fraction W/W_TO = 0.8997 (Main!S5), load factor n = 1 (Main!V5, input) and 100% afterburner (Main!W5, input).
- Rationale: Defines the service-ceiling design point on the constraint diagram (Consts row 25).
- Keywords: draft

#### REQ_F16A_014: Subsonic combat-turn point performance (Functional)
The aircraft shall sustain a load factor n of at least 4.5 (Main!V6, input) at Ps = 0 (Main!X6, input). This applies at these conditions: weight fraction W/W_TO = 0.8997 (Main!S6), altitude 20,000 ft (Main!T6, input), Mach 0.87 (Main!U6, input) and 100% afterburner (Main!W6). The formula =W5 sets this afterburner value to the setting of the Max-Altitude condition.
- Rationale: Defines subsonic sustained-turn maneuverability (Consts row 26).
- Keywords: draft

#### REQ_F16A_015: Supersonic combat-turn point performance (Functional)
The aircraft shall sustain a load factor n of at least 1.4 (Main!V7, input) at Ps = 0 (Main!X7, input). This applies at these conditions: weight fraction W/W_TO = 0.8997 (Main!S7), altitude 36,000 ft (Main!T7, input), Mach 1.4 (Main!U7, input) and 100% afterburner (Main!W7). The formula =W6 sets this afterburner value to the setting of the subsonic combat-turn condition.
- Rationale: Defines supersonic sustained-turn maneuverability (Consts row 27).
- Keywords: draft

#### REQ_F16A_016: Specific-excess-power point performance (Functional)
The aircraft shall achieve a specific excess power of at least 500 ft/s (Main!X8, input). This applies at these conditions: weight fraction W/W_TO = 0.8997 (Main!S8), altitude 10,000 ft (Main!T8, input), Mach 0.87 (Main!U8, input), 100% afterburner (Main!W8, set by the formula =W5) and load factor n = 1 (Main!V8, set by the formula =V5). Rows 9-10 (Main!R9:X10) use formulas to duplicate this condition. They are not independent requirements.
- Rationale: Defines the minimum energy maneuverability at a representative combat condition (Consts row 28). Rows 29-30 are a documented copy-and-paste duplicate.
- Keywords: draft

#### REQ_F16A_017: Takeoff field-length point performance (Functional)
The aircraft shall take off within a ground-roll distance of 4,000 ft (Main!X12, input). This applies at these conditions: sea level (Main!T12 = 0 ft, input), full takeoff weight (W/W_TO = 1, Main!S12, input), liftoff-speed factor V/V_stall = 1.2 (Main!U12, input), rolling-friction coefficient mu = 0.03 (Main!V12, input) and 100% afterburner (Main!W12, input).
- Rationale: Defines the available takeoff field length and the takeoff power and speed assumptions (Consts row 32).
- Keywords: draft

#### REQ_F16A_018: Landing field-length point performance (Functional)
The aircraft shall land within a ground-roll distance of 4,000 ft (Main!X13, input). This applies at these conditions: sea level (Main!T13 = 0 ft, input), full landing weight (W/W_TO = 1, Main!S13, input), approach-speed factor V/V_stall = 1.3 (Main!U13, input), braking-friction coefficient mu = 0.5 (Main!V13, input) and 0% afterburner (Main!W13, input).
- Rationale: Defines the available landing field length and the landing power and speed assumptions (Consts row 33).
- Keywords: draft

### REQ_F16A_STRUCT: Structural requirements (Container)
- Keywords: draft

#### REQ_F16A_019: Ultimate structural load factor (Functional)
The primary structure of the aircraft shall withstand an ultimate design load factor n_ult of 9 g (Main!Q27, input) without structural failure.
- Rationale: Sets the structural design envelope that is used to size the structural weights of the wing, fuselage and empennage (Wt tab).
- Keywords: draft

### REQ_F16A_WEIGHT: Weight and payload requirements (Container)
- Keywords: draft

#### REQ_F16A_020: Permanent payload capacity (Functional)
The aircraft shall carry a permanent (non-expended) payload of 700 lb (Main!O16, input).
- Rationale: Defines the fixed mission payload (for example, the gun and fixed avionics and equipment). The aircraft keeps this payload for the full mission, and the payload drives OEW.
- Keywords: draft

#### REQ_F16A_021: Expendable payload capacity (Functional)
The aircraft shall carry an expendable payload (stores) of 4,400 lb (Main!O17, input). The aircraft shall release this payload during the Combat mission segment (refer to REQ_F16A_006 and the Miss!I10 drop event).
- Rationale: Defines the capacity for mission stores and weapons. It also connects their release to the combat-segment event. This event drives the post-combat weight fraction and the egress performance.
- Keywords: draft

### REQ_F16A_MATERIALS: Materials requirements (Container)
- Keywords: draft

#### REQ_F16A_022: Composite material fraction limit (Functional)
The structural material mix of the airframe shall use composite materials (carbon fiber and fiberglass) for no more than 20% of the structural weight. The values are carbon fiber = 20% (Cost!B42, input) and fiberglass = 0% (Cost!B43, input). The remainder shall be Aluminum 65% (Cost!B41, input), Steel 5% (Cost!B44, input) and Titanium 10% (Cost!B45, input). All five fractions are direct Excel inputs, and their sum is 100% (Cost!B46, formula check).
- Rationale: Sets limits on the material technology assumptions in the material factor D47 of the DAPCA IV cost model (Cost tab). It also reflects the design philosophy of a legacy metallic airframe.
- Keywords: draft

### REQ_F16A_BALANCE: Balance requirements (Container)
- Keywords: draft

#### REQ_F16A_023: Tipback angle (TODO) (Functional)
TODO: The aircraft shall provide a main-gear tipback angle of at least TBD deg across the operational CG range. The criterion is blank on purpose. It is a standing student exercise (D-046). For reference only: the Brandt F-16A model (BrandtBalanceStabControl) computes approximately 21.5 deg. This value is an analysis output of the reference aircraft. It is not a design requirement value.
- Rationale: Makes sure that there is sufficient ground clearance and rotation margin during takeoff rotation, with no tail strike.
- Keywords: draft, todo

#### REQ_F16A_024: Rollover angle (TODO) (Functional)
TODO: The aircraft shall provide a rollover angle of at least TBD deg across the operational CG and gear track range. The criterion is blank on purpose. It is a standing student exercise (D-046). The exercise includes finding which convention the angle uses. For reference only: the Brandt F-16A model (BrandtBalanceStabControl) computes approximately 74.2 deg. This value is an analysis output of the reference aircraft. It is not a design requirement value.
- Rationale: Sets a limit on lateral ground stability (resistance to tip-over during crosswind taxi and turns).
- Keywords: draft, todo

### REQ_F16A_SC: Stability and control requirements (Container)
- Keywords: draft

#### REQ_F16A_025: Static margin (relaxed static stability) (Functional)
The aircraft shall have relaxed static stability. The static margin is SM = (x_np - x_cg)/MAC. SM shall satisfy -6 %MAC <= SM < 0 (CG aft of the neutral point) across the operational CG range, from takeoff to landing. This applies at both ends of the range, not to an average. The upper bound is strict. It is a definition, not a figure: relaxed static stability is a negative static margin. The -6 %MAC floor sets the maximum instability. This figure is an illustrative teaching value, not sourced data (D-030). It is the only invented number that remains, because D-051 removed the earlier +1 %MAC upper bound. When the aircraft burns fuel and releases stores, the CG moves forward (x_cg 26.1979 ft to 26.1451 ft). Thus landing is the forward, most stable end, and this requirement is most difficult to meet at that end. F16AStaticMarginVerificationTest checks both ends. The reference model does not meet this requirement. BrandtBalanceStabControl computes SM_TO = -0.26 %MAC (met) and SM_land = +0.21 %MAC (violated). This is because its neutral point is a simplified approximation (readme_bsc.md).
- Rationale: Relaxed static stability is a negative static margin. The CG is aft of the neutral point. This decreases trim drag and increases the instantaneous turn rate. The aircraft can fly in this condition only because the flight control system supplies artificial stability. The fly-by-wire decision of REQ_F16A_L02 is based on this premise. The -6 %MAC floor limits the instability to the level that the system is assumed to be able to stabilize. Without the floor, a requirement for only a negative margin would allow an aeroplane that nothing could fly. The requirement applies at both ends of the CG range, not to an average. Thus it stays true for the whole mission, not only when the aircraft is heavy. It also sizes the stabilator and sets limits on the permitted CG travel.
- Keywords: draft

### REQ_F16A_COST: Cost measure of merit (Container)
- Keywords: draft

#### REQ_F16A_026: Unit flyaway cost (minimize) (Functional)
Unit flyaway cost shall be minimized. This is a Measure of Merit (design objective), not a pass/fail threshold. A lower cost is always preferred. Cost is traded against weight, materials and production quantity. For reference only: the Brandt F-16A DAPCA IV model computes approximately $68.4M (program-year dollars) for the reference aircraft. This value is context. It is not an acceptance limit.
- Rationale: Cost is an objective to minimize. It drives the decisions about material, weight and production quantity. It is a Measure of Merit, not a 'shall not exceed' limit, because conceptual design trades affordability in this way. Its home is the Physical layer (D-043).
- Keywords: draft, moe, objective, minimize
