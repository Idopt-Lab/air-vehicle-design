# f16a_physical_derived
Requirements that the Physical layer (RFLP P) of the F-16A model owns and verifies. This set is kept separate from the sizing-derived set (f16a.slreqx), the functional-derived set and the logical-derived set.

## REQ_F16A_PHYSICAL: F-16A physical-layer requirements (Container)
Root container for the requirements that were found and verified at the Physical layer. Concrete parts and roll-up analyses exist at this layer to measure these requirements.
- Keywords: draft, derived, physical

### REQ_F16A_P01: Fuel volume sufficiency (Functional)
The aircraft shall have sufficient internal fuel tankage to carry the fuel that is required to complete the design mission profile (REQ_F16A_001-010). The tankage is a volume, given as a fuel-weight capacity. The aircraft shall not rely on external tanks. Verification method: the total available fuel capacity (a roll-up over the internal fuel tanks) shall be greater than or equal to the required mission fuel (from the mission analysis).
- Rationale: Range and endurance closure depend on carrying sufficient fuel. The check belongs at P, because it needs concrete tanks from which to roll up an available capacity. Both sides are now real numbers. The tanks roll up to 6300 lb, and the mission analysis burns approximately 5960 lb. Thus the requirement is met with approximately 340 lb of margin (D-060).
- Keywords: draft, derived, physical

### REQ_F16A_P02: Life-cycle cost (Functional)
The life-cycle cost of the aircraft shall be quantified for the design mission profile (REQ_F16A_001-010). Life-cycle cost is the unit flyaway cost plus the operating and support cost over the service life. Verification method: MeasureOfMerit.LifeCycleCost_USD on the aircraft. F16APhysicalCostModel computes this value from the rolled-up empty weight of this model and from its mission fuel and sortie time. No cost ceiling is stated. No sourced affordability target exists for this example, and to invent one would be to invent a requirement.
- Rationale: Mission fuel has an effect on cost through only one path: the operating and support terms. Thus only three cost Measures of Merit change when the mission changes: OMCostAnnual_USD, OMCostLife_USD and LifeCycleCost_USD. The unit flyaway cost does not change (D-043, D-061). Without this requirement, LifeCycleCost_USD would be on the aircraft with no trace to a requirement. Cross-check: the life-cycle figure of BrandtCost is approximately $93.26M.
- Keywords: draft, derived, physical
