# F16A

## #1: F - Threat (Functional)
Eliminate Threat

### #2: R - Detect (Functional)
Aircraft needs to “detect” an enemy threat at a distance of 100 nautical miles

### #8: R - Target (Functional)
Aircraft needs to "target" an enemy threat at a distance of 100 nautical miles

### #9: R - Engage (Functional)
Aircraft needs to "engage" the enemy threat at a distance of 100 nautical miles

### #10: R - Verify (Functional)
Aircraft needs to "verify" the enemy threat is eliminated

## #3: F- Structure/Loads (Functional)
Ensure strength/durability across combat envelope

### #4: R-Structure (Functional)
Design load limits +9 g / –3 g, withstand q = 2,133 psf, FoS = 1.5

## #5: F - Propulsion (Functional)
High thrust-to-weight turbofan

### #6: R - Propulsion (Functional)
Provide thrust for Mach 1.6 at 36,000 ft, sustained maneuvering, and rapid climb
